// SPDX-License-Identifier: BSD-2-Clause
submodule frr-bgp-common-structure {
  yang-version 1.1;

  belongs-to frr-bgp {
    prefix "bgp";
  }

  import ietf-inet-types {
    prefix inet;
  }

  import frr-route-map {
    prefix frr-route-map;
  }

  import frr-interface {
    prefix frr-interface;
  }

  import frr-bfdd {
    prefix frr-bfdd;
  }

  import ietf-bgp-types {
    prefix bt;
  }

  import frr-bgp-types {
    prefix frr-bt;
  }

  include "frr-bgp-common";

  organization
    "FRRouting";
  contact
    "FRR Users List: <mailto:frog@lists.frrouting.org> FRR Development
     List: <mailto:dev@lists.frrouting.org>";
  description
    "This submodule contains general data definitions for use in BGP.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2026-07-21 {
    description
      "Sync neighbor/peer-group session and AF policy options with
       current FRR CLI (roles, TCP-MSS, BFD profile, addpath RX,
       conditional advertisement, ...).";
    reference
      "FRRouting";
  }

  revision 2019-12-03 {
    description
      "Initial revision.";
    reference
      "FRRouting";
  }

  grouping structure-neighbor-group-ebgp-multihop {
    description
      "Structural grouping used to include EBGP multi-hop
       configuration for both BGP neighbors and peer groups.";
    container ebgp-multihop {
      description
        "EBGP multi-hop parameters for the BGP group.";
      choice hop-count-choice {
        description
          "Choice for EBGP multihop TTL configuration.";
        case default-hop-count {
          leaf enabled {
            type boolean;
            default "false";
            description
              "When enabled the referenced group or neighbors are
               permitted to be indirectly connected - including cases
               where the TTL can be decremented between the BGP peers.";
          }
        }

        case max-hop-count {
          leaf multihop-ttl {
            type uint8 {
              range "1..255";
            }
            description
              "Time-to-live value to use when packets are sent to the
               referenced group or neighbors and ebgp-multihop is
               enabled.";
          }
        }
      }

      leaf disable-connected-check {
        type boolean;
        default "false";
        description
          "When set to 'true' it enforces EBGP neighbors perform multihop.";
      }
    }
  }

  grouping neighbor-local-as-options {
    description
      "Configuration options for local AS number for BGP neighbors.";
    container local-as {
      description
        "Local AS number configuration parameters.";
      leaf local-as {
        type inet:as-number;
        description
          "The local autonomous system number that is to be used when
           establishing sessions with the remote peer or peer group, if
           this differs from the global BGP router autonomous system
           number.";
      }

      leaf no-prepend {
        type boolean;
        default "false";
        description
          "Do not prepend local-as to updates from EBGP peers. When
           set to 'true' it will not prepend local-as to updates. When
           set to 'false' it will prepend local-as to updates.";
      }

      leaf replace-as {
        type boolean;
        default "false";
        description
          "Do not prepend local-as to updates from IBGP peers.";
      }

      leaf dual-as {
        type boolean;
        default "false";
        description
          "Accept either the global BGP AS or local-as in the remote
           OPEN. Maps to: neighbor <peer> local-as <asn> dual-as.";
      }
    }
  }

  grouping neighbor-bfd-options {
    description
      "BFD options for BGP neighbors.";
    container bfd-options {
      description
        "BFD configuration parameters.";
      leaf enable {
        type boolean;
        default "false";
        description
          "BFD support.";
      }

      leaf detect-multiplier {
        when "../enable = 'true'";
        type uint8 {
          range "2..255";
        }
        default "3";
        description
          "Detect multiplier.";
      }

      leaf required-min-rx {
        when "../enable = 'true'";
        type uint16 {
          range "50..60000";
        }
        units "milliseconds";
        default "300";
        description
          "Required min receive interval.";
      }

      leaf desired-min-tx {
        when "../enable = 'true'";
        type uint16 {
          range "50..60000";
        }
        units "milliseconds";
        default "300";
        description
          "Desired min transmit interval.";
      }

      leaf session-type {
        when "../enable = 'true'";
        type frr-bt:bfd-session-type;
        default "not-configured";
        description
          "BFD session type.";
      }

      leaf check-cp-failure {
        when "../enable = 'true'";
        type boolean;
        default "false";
        description
          "Link dataplane status with BGP control plane.";
      }

      leaf profile {
        type frr-bfdd:profile-ref;
        description
          "BFD profile applied to this BGP neighbor or peer group.
           Maps to: neighbor <peer> bfd profile <profile>.";
      }

      leaf strict-mode {
        type boolean;
        default "false";
        description
          "Require BFD to be established before the BGP session is
           usable. Maps to: neighbor <peer> bfd strict.";
      }

      leaf strict-hold-time {
        when "../strict-mode = 'true'";
        type uint32 {
          range "1..4294967295";
        }
        units "seconds";
        description
          "Time to wait before declaring BFD down in BFD strict mode.
           Maps to: neighbor <peer> bfd strict hold-time
           <1-4294967295>.";
      }
    }
  }

  grouping neighbor-remote-as {
    description
      "Configuration for remote AS number for BGP neighbors.";
    container neighbor-remote-as {
      description
        "Remote AS number configuration parameters.";
      leaf remote-as-type {
        type frr-bt:as-type;
        description
          "Remote AS type.";
      }

      leaf remote-as {
        when "../remote-as-type = 'as-specified'";
        type inet:as-number;
        description
          "The remote autonomous system number received in
           the BGP OPEN message.";
        reference
          "RFC 4271";
      }
    }
  }

  grouping neighbor-update-source {
    description
      "Source of routing updates.";
    container update-source {
      description
        "Source of routing updates config.";
      choice source {
        description
          "Source type for routing updates.";
        case ip-based {
          leaf ip {
            type inet:ip-address;
            description
              "IPv4 address/IPv6 address.";
          }
        }

        case interface-based {
          leaf interface {
            type frr-interface:interface-ref {
              require-instance false;
            }
            description
              "The local interface.";
          }
        }
      }
    }
  }

  grouping structure-neighbor-group-add-paths {
    description
      "Structural grouping used to include ADD-PATHs configuration
       and state for both BGP neighbors and peer groups.";
    container add-paths {
      description
        "Parameters relating to the advertisement and receipt of
         multiple paths for a single NLRI (add-paths).";
      reference
        "RFC 7911: ADD-PATH.";
      leaf path-type {
        type frr-bt:add-path-type;
        default "none";
        description
          "Enable ability to receive multiple path advertisements for
           an NLRI from the neighbor or group.";
      }

      leaf best-selected-paths {
        when "../path-type = 'best-selected'";
        type uint8 {
          range "1..6";
        }
        description
          "Number of best selected paths to advertise with addpath.
           Maps to: neighbor <peer> addpath-tx-best-selected <1-6>.";
      }

      leaf disable-addpath-rx {
        type boolean;
        default "false";
        description
          "Do not accept additional paths from this peer.
           Maps to: neighbor <peer> disable-addpath-rx.";
      }

      leaf addpath-rx-paths-limit {
        type uint16 {
          range "1..65535";
        }
        description
          "Maximum number of additional paths to receive from this peer.
           Maps to: neighbor <peer> addpath-rx-paths-limit <1-65535>.";
      }
    }
  }

  grouping structure-neighbor-group-as-path-options {
    description
      "Structural grouping used to include AS_PATH manipulation
       configuration both BGP neighbors and peer groups.";
    container as-path-options {
      description
        "AS_PATH manipulation parameters for the BGP neighbor or
         group.";
      choice allowas-in {
        description
          "Options for allowing own AS in AS_PATH.";
        case occurence-based {
          leaf allow-own-as {
            type uint8 {
              range "1..10";
            }
            description
              "Specify the number of occurrences of the local BGP
               speaker's AS that can occur within the AS_PATH before it
               is rejected.";
          }
        }

        case origin-based {
          leaf allow-own-origin-as {
            type boolean;
            default "false";
            description
              "When set to 'true' only accept my AS in the as-path
               if the route was originated in my AS.";
          }
        }
      }

      leaf allowas-in-route-map {
        type frr-route-map:route-map-ref;
        description
          "Optional route-map that gates allowas-in processing.
           Maps to: neighbor <peer> allowas-in route-map <name> ...";
      }

      leaf replace-peer-as {
        type boolean;
        default "false";
        description
          "Replace occurrences of the peer's AS in the AS_PATH with
           the local autonomous system number. This is same as override
           ASN CLI.";
      }
    }
  }

  grouping structure-neighbor-group-capability-options {
    description
      "Structural grouping used to include capability
       configuration for both BGP neighbors and peer groups.";
    container capability-options {
      description
        "Capability manipulation parameters for the BGP neighbor or
         group.";
      leaf dynamic-capability {
        type boolean;
        default "false";
        description
          "When set to 'true' dynamic capability is advertise to this peer.";
      }

      leaf strict-capability {
        type boolean;
        default "false";
        description
          "Strict capability negotiation match. When set to 'true'
           remote and local capabilities are strictly compared
           if capabilities are different, send Unsupported Capability
           error then reset connection.";
      }

      leaf extended-nexthop-capability {
        type boolean;
        default "false";
        description
          "When set to 'true' extended next-hop capability is advertise
           to this peer.";
      }

      leaf capability-negotiate {
        type boolean;
        default "true";
        description
          "When set to 'true' sending Capability Negotiation in the open
           message is suppressed to this peer.";
      }

      leaf override-capability {
        type boolean;
        default "false";
        description
          "Overrides the result of Capability Negotiation, ignoring remote
           peer's capability value, when set to 'true'.";
      }

      leaf fqdn-capability {
        type boolean;
        default "true";
        description
          "Advertise the FQDN capability to this peer.
           Maps to: neighbor <peer> capability fqdn.
           Default true matches peer_create() which enables FQDN
           unless explicitly disabled.";
      }

      leaf software-version-capability {
        type enumeration {
          enum disabled {
            description
              "Do not advertise the software-version capability
               (explicit override of bgp default).";
          }
          enum old-encoding {
            description
              "Advertise the legacy software-version capability
               encoding.";
          }
          enum latest-encoding {
            description
              "Advertise the latest software-version capability
               encoding.";
          }
        }
        description
          "Advertise the software-version capability to this peer.
           Maps to: neighbor <peer> capability software-version
           [latest-encoding]. Absent means inherit from
           'bgp default software-version-capability'.";
      }

      leaf link-local-capability {
        type boolean;
        default "false";
        description
          "Advertise the Link-Local Next Hop capability to this peer.
           Maps to: neighbor <peer> capability link-local.";
      }
    }
  }

  grouping structure-neighbor-group-session-options {
    description
      "Structural grouping used to include session configuration for
       both BGP neighbors and peer groups.";

    leaf tcp-mss {
      type uint16 {
        range "1..65535";
      }
      description
        "TCP maximum segment size for the BGP session.
         Maps to: neighbor <peer> tcp-mss <1-65535>.";
    }

    leaf ip-transparent {
      type boolean;
      default "false";
      description
        "Enable IP_TRANSPARENT on the BGP TCP socket.
         Maps to: neighbor <peer> ip-transparent.";
    }

    container local-role {
      description
        "BGP Open Policy role configuration.";

      leaf role {
        type frr-bt:bgp-role;
        description
          "Local BGP role used for role capability negotiation and
           Only-To-Customer attribute processing.
           Maps to: neighbor <peer> local-role
           <provider|rs-server|rs-client|customer|peer>.";
      }

      leaf strict-mode {
        when "../role";
        type boolean;
        default "false";
        description
          "Require the remote peer to advertise a compatible BGP role.
           Maps to: neighbor <peer> local-role <role> strict-mode.";
      }
    }

    leaf rpki-strict {
      type boolean;
      default "false";
      description
        "Require RPKI validation information for this peer.
         Maps to: neighbor <peer> rpki strict.";
    }

    leaf aigp {
      type boolean;
      default "false";
      description
        "Enable send and receive of the AIGP attribute for this peer.
         Maps to: neighbor <peer> aigp.";
    }

    leaf extended-link-bandwidth {
      type boolean;
      default "false";
      description
        "Send the extended (64-bit) Link-Bandwidth encoding.
         Maps to: neighbor <peer> extended-link-bandwidth.";
    }

    leaf disable-link-bw-encoding-ieee {
      type boolean;
      default "false";
      description
        "Disable IEEE floating-point encoding for Link-Bandwidth
         extended communities.
         Maps to: neighbor <peer> disable-link-bw-encoding-ieee.";
    }

    leaf extended-optional-parameters {
      type boolean;
      default "false";
      description
        "Force the extended optional parameters format for OPEN
         messages. Maps to: neighbor <peer> extended-optional-parameters.";
    }

    leaf send-nexthop-characteristics {
      type boolean;
      default "false";
      description
        "Send the BGP Next Hop Dependent Characteristics attribute.
         Maps to: neighbor <peer> send-nexthop-characteristics.";
    }

    leaf sender-as-path-loop-detection {
      type boolean;
      default "false";
      description
        "Detect AS-path loops before sending routes to this peer.
         Maps to: neighbor <peer> sender-as-path-loop-detection.";
    }

    leaf oad {
      type boolean;
      default "false";
      description
        "Mark the session as EBGP-OAD (Old Autonomous Domain).
         Maps to: neighbor <peer> oad.";
    }

    leaf graceful-shutdown {
      type boolean;
      default "false";
      description
        "Enable graceful-shutdown for this peer.
         Maps to: neighbor <peer> graceful-shutdown.";
    }
  }

  grouping structure-neighbor-group-path-attribute-options {
    description
      "Structural grouping used to include inbound path attribute
       error handling configuration for both BGP neighbors and peer
       groups.";

    container path-attribute {
      description
        "Handling of selected path attributes in received UPDATE
         messages.";

      leaf-list discard {
        type uint8 {
          range "1..255";
        }
        description
          "Discard the specified path attribute from received UPDATE
           messages.
           Maps to: neighbor <peer> path-attribute discard <1-255>...";
      }

      leaf-list treat-as-withdraw {
        type uint8 {
          range "1..255";
        }
        description
          "Treat received UPDATE messages containing the specified path
           attribute as withdrawals.
           Maps to: neighbor <peer> path-attribute treat-as-withdraw
           <1-255>...";
      }
    }
  }

  grouping structure-neighbor-group-af-policy-options {
    description
      "Structural grouping used to include AF-specific BGP policy
       options for both neighbors and peer groups.";

    container conditional-advertisement {
      description
        "Conditional route advertisement configuration.";

      leaf advertise-map {
        type frr-route-map:route-map-ref;
        description
          "Route-map selecting routes to advertise conditionally.
           Maps to: neighbor <peer> advertise-map <route-map>
           <exist-map|non-exist-map> <route-map>.";
      }

      choice condition {
        description
          "Condition used to enable conditional advertisement.";

        case exist-map {
          leaf exist-map {
            type frr-route-map:route-map-ref;
            description
              "Advertise when the route-map matches an installed BGP
               route.
               Maps to: neighbor <peer> advertise-map <route-map>
               exist-map <route-map>.";
          }
        }

        case non-exist-map {
          leaf non-exist-map {
            type frr-route-map:route-map-ref;
            description
              "Advertise when the route-map does not match an installed
               BGP route.
               Maps to: neighbor <peer> advertise-map <route-map>
               non-exist-map <route-map>.";
          }
        }
      }
    }

    leaf accept-own {
      type boolean;
      default "false";
      description
        "Accept self-originated VPN routes carrying the ACCEPT_OWN
         community. Maps to: neighbor <peer> accept-own.";
    }

    leaf soo {
      type string;
      description
        "Site-of-Origin extended community.
         Maps to: neighbor <peer> soo <asn:nn|ip-address:nn>.";
    }

    leaf upa {
      type boolean;
      default "false";
      description
        "Send Unreachable Prefix Announcement routes to this peer.
         Maps to: neighbor <peer> upa.";
    }
  }

  grouping structure-neighbor-default-originate-options {
    description
      "Structural grouping used to include default-originate
       configuration for both BGP neighbors and peer groups.";
    container default-originate {
      description
        "default originate parameters for the BGP neighbor or
         group.";
      leaf originate {
        type boolean;
        default "false";
        description
          "If set to 'true', send the default-route to the neighbour(s).";
      }

      leaf route-map {
        type frr-route-map:route-map-ref;
        description
          "Route-map to specify criteria to originate default.";
      }
    }
  }

  grouping structure-neighbor-prefix-limit {
    description
      "Configuration for prefix limits for BGP neighbors.";
    container prefix-limit {
      description
        "Parameters relating to the prefix limit for the AFI-SAFI.";
      list direction-list {
        key "direction";
        description
          "List of prefix limit directions.";
        leaf direction {
          type frr-bt:direction;
          description
            "Prefix limit applied on Tx route-updates or Rx route-updates.";
        }

        leaf max-prefixes {
          type uint32;
          mandatory true;
          description
            "Maximum number of prefixes that will be accepted from the
             neighbour.";
        }

        leaf force-check {
          type boolean;
          default false;
          description
            "Force check all received routes.";
        }

        container options {
          when "../direction = 'in'";
          description
            "Options for prefix limit handling.";
          choice options {
            description
              "Prefix limit options.";
            case warning {
              leaf warning-only {
                type boolean;
                default "false";
                description
                  "When set to 'true' only give warning message when limit
                   is exceeded.";
              }
            }

            case restart {
              leaf restart-timer {
                type uint16;
                units "minutes";
                description
                  "Time interval in seconds after which the BGP session is
                   re-established after being torn down due to exceeding the
                   max-prefix limit.";
              }
            }

            case threshold {
              leaf shutdown-threshold-pct {
                type bt:percentage;
                description
                  "Threshold on number of prefixes that can be received from
                   a neighbour before generation of warning messages or log
                   entries. Expressed as a percentage of max-prefixes.";
              }
            }

            case threshold-restart {
              leaf tr-shutdown-threshold-pct {
                type bt:percentage;
                description
                  "Threshold on number of prefixes that can be received from
                   a neighbour before generation of warning messages or log
                   entries. Expressed as a percentage of max-prefixes.";
              }

              leaf tr-restart-timer {
                type uint16;
                units "minutes";
                description
                  "Time interval in seconds after which the BGP session is
                   re-established after being torn down due to exceeding the
                   max-prefix limit.";
              }
            }

            case threshold-warning {
              leaf tw-shutdown-threshold-pct {
                type bt:percentage;
                description
                  "Threshold on number of prefixes that can be received from
                   a neighbour before generation of warning messages or log
                   entries. Expressed as a percentage of max-prefixes.";
              }

              leaf tw-warning-only {
                type boolean;
                default "false";
                description
                  "When set to 'true' only give warning message when limit
                   is exceeded.";
              }
            }
          }
        }
      }
    }
  }

  grouping structure-neighbor-nexthop-self {
    description
      "Configuration for nexthop-self for BGP neighbors.";
    container nexthop-self {
      description
        "Parameters relating to the nexthop-self for the AFI-SAFI.";
      leaf next-hop-self {
        type boolean;
        default "false";
        description
          "When set to 'true', EBGP learned routes are announced with the
           local speaker's nexthop.";
      }

      leaf next-hop-self-force {
        type boolean;
        default "false";
        description
          "When set to 'true', EBGP learned routes are announced with the
           local speaker's nexthop.";
      }
    }
  }

  grouping structure-neighbor-private-as {
    description
      "Configuration for private AS handling for BGP neighbors.";
    container private-as {
      description
        "Parameters relating to the private-as for the AFI-SAFI.";
      leaf remove-private-as-all {
        type boolean;
        default "false";
        description
          "When set to 'true', private ASNs are removed from outbound updates;
           applies to all AS numbers.";
      }

      leaf remove-private-as-all-replace {
        type boolean;
        default "false";
        description
          "When set to 'true', private ASNs are replaced by the local
           speaker's ASN in all outbound updates; applies to all AS numbers.";
      }

      leaf remove-private-as {
        type boolean;
        default "false";
        description
          "When set to 'true', removes private ASNs in outbound updates;
           applies to all AS numbers.";
      }

      leaf remove-private-as-replace {
        type boolean;
        default "false";
        description
          "When set to 'true', private ASNs are replaced with the local
           speaker's ASN in all outbound updates; applies to all AS numbers.";
      }
    }
  }

  grouping structure-neighbor-weight {
    description
      "Configuration for weight attribute for BGP neighbors.";
    container weight {
      description
        "Parameters relating to the weight for the AFI-SAFI.";
      leaf weight-attribute {
        type uint16 {
          range "0..65535";
        }
        description
          "Set default weight for routes from this neighbor.";
      }
    }
  }

  grouping structure-neighbor-route-reflector {
    description
      "Configuration for route reflector for BGP neighbors.";
    container route-reflector {
      description
        "Parameters relating to the route-reflector for the AFI-SAFI.";
      leaf route-reflector-client {
        type boolean;
        default "false";
        description
          "Configure a neighbor as route reflector client.";
      }
    }
  }

  grouping structure-neighbor-route-server {
    description
      "Configuration for route server for BGP neighbors.";
    container route-server {
      description
        "Parameters relating to the route-server for the AFI-SAFI.";
      leaf route-server-client {
        type boolean;
        default "false";
        description
          "Configure a neighbor as route server client.";
      }
    }
  }

  grouping structure-neighbor-send-community {
    description
      "Configuration for sending community attributes for BGP neighbors.";
    container send-community {
      description
        "Parameters relating to the send-community for the AFI-SAFI.";
      leaf send-community {
        type boolean;
        default "true";
        description
          "Send standard community attribute to this neighbor.";
      }

      leaf send-ext-community {
        type boolean;
        default "true";
        description
          "Send extended community attribute to this neighbor.";
      }

      leaf send-large-community {
        type boolean;
        default "true";
        description
          "Send large community attribute to this neighbor.";
      }

      leaf send-ext-community-rpki {
        type boolean;
        default "false";
        description
          "Send RPKI extended communities to this peer.
           Maps to: neighbor <peer> send-community extended rpki.";
      }
    }
  }

  grouping structure-neighbor-group-admin-shutdown {
    description
      "Structural grouping used to include admin-shutdown
       configuration for both BGP neighbors and peer groups.";
    container admin-shutdown {
      description
        "BGP Administrative Shutdown Communication.";
      leaf enable {
        type boolean;
        description
          "When set to 'true', BGP shutdown communication is enabled.";
      }

      leaf message {
        type string;
        description
          "Shutdown message.";
        reference
          "draft-ietf-idr-shutdown-06";
      }

      leaf rtt {
        type uint16 {
          range "1..65535";
        }
        units "milliseconds";
        description
          "Shut down the peer when round-trip-time exceeds this
           threshold. Maps to: neighbor ... shutdown rtt (1-65535)
           [count (1-255)].";
      }

      leaf rtt-count {
        when "../rtt";
        type uint8 {
          range "1..255";
        }
        default "1";
        description
          "Number of consecutive keepalives with RTT above the
           threshold before shutting down the peer.
           Maps to: neighbor ... shutdown rtt ... count (1-255).";
      }
    }
  }

  grouping structure-neighbor-group-graceful-restart {
    description
      "Structural grouping used to include graceful-restart
       configuration for both BGP neighbors and peer groups.";
    container graceful-restart {
      description
        "BGP Graceful restart feature.";
      choice mode {
        description
          "Graceful restart mode selection.";
        case graceful-restart-mode {
          leaf enable {
            type boolean;
            default "false";
            description
              "Enable or disable the graceful-restart capability.
               Setting this value to 'true' enables the graceful-restart
               and helper both at peer level. Setting this value to 'false'
               disables graceful restart and helper mode. The peer will inherit
               global configuration.";
          }
        }

        case graceful-restart-helper-mode {
          leaf graceful-restart-helper {
            type boolean;
            default "false";
            description
              "Setting this value to 'true' enables helper mode for the peer
               Setting this value to 'false' disables the helper mode. The
               peer will inherit global configuration.";
          }
        }

        case graceful-restart-disable-mode {
          leaf graceful-restart-disable {
            type boolean;
            default "false";
            description
              "Setting this value to 'true' disables the graceful-restart
               and helper Mode. Setting this value to 'false' causes the peer
               to inherit global configuration.";
          }
        }
      }
    }
  }

  grouping structure-neighbor-group-soft-reconfiguration {
    description
      "Structural grouping used to include soft-reconfiguration
       configuration for both BGP neighbors and peer groups.";
    leaf soft-reconfiguration {
      type boolean;
      default "false";
      description
        "Allow inbound soft reconfiguration for this neighbor.";
    }
  }

  grouping structure-neighbor-group-attr-unchanged {
    description
      "Structural grouping used to include BGP route propagation
       rules configuration for both BGP neighbors and peer groups.";
    container attr-unchanged {
      description
        "BGP route propagation rules configuration.";
      leaf as-path-unchanged {
        type boolean;
        default "false";
        description
          "When set to 'true' as-path attribute is propagated unchanged.";
      }

      leaf next-hop-unchanged {
        type boolean;
        default "false";
        description
          "When set to 'true' next-hop attribute is propagated unchanged.";
      }

      leaf med-unchanged {
        type boolean;
        default "false";
        description
          "When set to 'true' med attribute is propagated unchanged.";
      }
    }
  }

  grouping structure-neighbor-group-orf-capability {
    description
      "Structural grouping used to include orf
       configuration for both BGP neighbors and peer groups.";
    container orf-capability {
      description
        "Outbound Route Filtering capability configuration.";
      choice orf-update {
        description
          "ORF update direction options.";
        case send {
          leaf orf-send {
            type boolean;
            default "false";
            description
              "Setting to 'true' advertises the ORF capability.";
          }
        }

        case receive {
          leaf orf-receive {
            type boolean;
            default "false";
            description
              "When set to 'true' it receives the orf capability.";
          }
        }

        case both {
          leaf orf-both {
            type boolean;
            default "false";
            description
              "When set to 'true' it advertises/receives the orf capability.";
          }
        }
      }
    }
  }

  grouping structure-neighbor-config-timers {
    description
      "Structural grouping used to include per neighbor timers
       configuration for both BGP neighbors and peer groups.";
    container timers {
      description
        "Timer configuration parameters.";
      leaf advertise-interval {
        type uint16 {
          range "0..600";
        }
        units "seconds";
        description
          "Minimum interval between sending BGP routing updates.";
      }

      leaf connect-time {
        type uint16 {
          range "1..65535";
        }
        units "seconds";
        description
          "BGP connect timer.";
      }

      leaf delayopen {
        type uint16 {
          range "1..240";
        }
        units "seconds";
        description
          "Delay sending the BGP OPEN message after TCP connection
           setup. Maps to: neighbor <peer> timers delayopen <1-240>.";
      }

      uses neighbor-timers;
    }
  }

  grouping structure-neighbor-group-encapsulation {
    description
      "Structural grouping for neighbor encapsulation preference
       (MPLS vs SRv6).";

    container encapsulation {
      description
        "Preferred encapsulation for routes advertised to this peer.
         Maps to: neighbor <peer> encapsulation-mpls|
         encapsulation-srv6|encapsulation-srv6-relax.
         MPLS and SRv6 may both be configured (classic CLI); srv6 and
         srv6-relax remain mutually exclusive.";

      leaf-list type {
        type enumeration {
          enum mpls {
            description
              "Prefer MPLS encapsulation.
               Maps to: encapsulation-mpls.";
          }
          enum srv6 {
            description
              "Prefer SRv6 encapsulation.
               Maps to: encapsulation-srv6.";
          }
          enum srv6-relax {
            description
              "Advertise routes with and without SRv6 prefix SID.
               Maps to: encapsulation-srv6-relax.";
          }
        }
        description
          "Encapsulation type(s). Multiple values allowed so MPLS and
           SRv6 can be set together.";
      }
    }
  }

  grouping structure-neighbor-group-filter-config {
    description
      "Structural grouping used to include filter
       configuration for both BGP neighbors and peer groups.";
    container filter-config {
      description
        "BGP Policy configuration for both BGP neighbors and groups.";
      uses rmap-policy-import;

      uses rmap-policy-export;

      uses plist-policy-import;

      uses plist-policy-export;

      uses access-list-policy-import;

      uses access-list-policy-export;

      uses as-path-filter-list-policy-import;

      uses as-path-filter-list-policy-export;

      uses unsuppress-map-policy-import;

      uses unsuppress-map-policy-export;
    }
  }
}
