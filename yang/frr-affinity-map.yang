// SPDX-License-Identifier: BSD-2-Clause
module frr-affinity-map {
  yang-version 1.1;
  namespace "http://frrouting.org/yang/affinity-map";
  prefix frr-affinity-map;

  organization
    "FRRouting";
  contact
    "FRR Users List:       <mailto:frog@lists.frrouting.org>
     FRR Development List: <mailto:dev@lists.frrouting.org>";
  description
    "This module defines route map settings

     Copyright 2022 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2022-11-03 {
    description
      "Initial revision";
    reference "FRRouting";
  }

  typedef affinity-map-ref {
    type leafref {
      path "/frr-affinity-map:lib/frr-affinity-map:affinity-maps/frr-affinity-map:affinity-map/frr-affinity-map:name";
      require-instance true;
    }
    description
      "Reference to an affinity map";
  }

  container lib {
    description "Affinity map library";
    container affinity-maps {
      description
        "Affinity Mapping Table";
      list affinity-map {
        key "name";
        unique "value";
        description
          "Affinity Mapping configuration";
        leaf name {
          type string {
            length "1..32";
          }
          description
            "Affinity Name";
        }
        leaf value {
          type uint16 {
            range "0..1023";
          }
          mandatory true;
          description
            "Bit position";
        }
      }
    }
  }
}
