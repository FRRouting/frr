module frr-pim-route-map {
  yang-version 1.1;
  namespace "http://frrouting.org/yang/pim-route-map";
  prefix frr-pim-route-map;

  import ietf-inet-types {
    prefix inet;
  }

  import frr-route-map {
    prefix frr-route-map;
  }

  import frr-interface {
    prefix frr-interface;
  }

  import frr-filter {
    prefix frr-filter;
  }

  organization
    "FRRouting";
  contact
    "FRR Users List:       <mailto:frog@lists.frrouting.org>
     FRR Development List: <mailto:dev@lists.frrouting.org>";

  description
    "This module defines YANG augmentations for PIM route-map functionality.
     It extends the FRR route-map module to support multicast-specific
     match conditions for both IPv4 and IPv6 addresses, including source
     and group address matching, prefix list matching, and interface-based filtering.";

  revision 2021-08-25 {
    description
      "Initial revision";

    reference
      "FRRouting";
  }

  identity ipv4-multicast-source {
    base frr-route-map:rmap-match-type;
    description
      "Match multicast IPv4 source address";
  }

  identity ipv6-multicast-source {
    base frr-route-map:rmap-match-type;
    description
      "Match multicast IPv6 source address";
  }

  identity ipv4-multicast-source-prefix-list {
    base frr-route-map:rmap-match-type;
    description
      "Match multicast IPv4 source prefix list";
  }

  identity ipv6-multicast-source-prefix-list {
    base frr-route-map:rmap-match-type;
    description
      "Match multicast IPv6 source prefix list";
  }

  identity ipv4-multicast-group {
    base frr-route-map:rmap-match-type;
    description
      "Match multicast IPv4 group address";
  }

  identity ipv6-multicast-group {
    base frr-route-map:rmap-match-type;
    description
      "Match multicast IPv6 group address";
  }

  identity ipv4-multicast-group-prefix-list {
    base frr-route-map:rmap-match-type;
    description
      "Match multicast IPv4 group prefix list";
  }

  identity ipv6-multicast-group-prefix-list {
    base frr-route-map:rmap-match-type;
    description
      "Match multicast IPv6 group prefix list";
  }

  identity multicast-interface {
    base frr-route-map:rmap-match-type;
    description
      "Match multicast interface";
  }

  identity multicast-source-interface {
    base frr-route-map:rmap-match-type;
    description
      "Match the multicast source interface for the route-map evaluation context.";
  }

  augment "/frr-route-map:lib/frr-route-map:route-map/frr-route-map:entry/frr-route-map:match-condition/frr-route-map:rmap-match-condition/frr-route-map:match-condition" {
    description
      "Augments the route-map match-condition to support PIM-specific match types
       for multicast routing. This includes matching IPv4/IPv6 multicast source
       addresses, group addresses, prefix lists, and interfaces.";

    case multicast-source {
      when "derived-from-or-self(../frr-route-map:condition, 'frr-pim-route-map:ipv4-multicast-source')";

      leaf ipv4-multicast-source-address {
        type inet:ipv4-address;
        description
          "IPv4 multicast source address to match";
      }
    }

    case multicast-source-v6 {
      when "derived-from-or-self(../frr-route-map:condition, 'frr-pim-route-map:ipv6-multicast-source')";

      leaf ipv6-multicast-source-address {
        type inet:ipv6-address;
        description
          "IPv6 multicast source address to match";
      }
    }

    case multicast-group {
      when "derived-from-or-self(../frr-route-map:condition, 'frr-pim-route-map:ipv4-multicast-group')";

      leaf ipv4-multicast-group-address {
        type inet:ipv4-address;
        description
          "IPv4 multicast group address to match";
      }
    }

    case multicast-group-v6 {
      when "derived-from-or-self(../frr-route-map:condition, 'frr-pim-route-map:ipv6-multicast-group')";

      leaf ipv6-multicast-group-address {
        type inet:ipv6-address;
        description
          "IPv6 multicast group address to match";
      }
    }

    case multicast-interface {
      when "derived-from-or-self(../frr-route-map:condition, 'frr-pim-route-map:multicast-interface')";

      leaf multicast-interface {
        type frr-interface:interface-ref;
        description
          "Multicast interface to match";
      }
    }

    case multicast-source-interface {
      when "derived-from-or-self(../frr-route-map:condition, 'frr-pim-route-map:multicast-source-interface')";

      leaf multicast-source-interface {
        type frr-interface:interface-ref;
        description
          "Multicast source interface to match for the route-map evaluation context.";
      }
    }

    case prefix-list-name {
      when "derived-from-or-self(../frr-route-map:condition, 'frr-pim-route-map:ipv4-multicast-source-prefix-list') or "
      + "derived-from-or-self(../frr-route-map:condition, 'frr-pim-route-map:ipv6-multicast-source-prefix-list') or "
      + "derived-from-or-self(../frr-route-map:condition, 'frr-pim-route-map:ipv4-multicast-group-prefix-list') or "
      + "derived-from-or-self(../frr-route-map:condition, 'frr-pim-route-map:ipv6-multicast-group-prefix-list')";

      leaf list-name {
        type frr-filter:prefix-list-ref;
        description
          "Prefix list name to match";
      }
    }
  }
}
