// SPDX-License-Identifier: BSD-2-Clause
module frr-module-translator {
  yang-version 1.1;
  namespace "http://frrouting.org/yang/frr-module-translator";
  prefix frr-module-translator;

  organization
    "FRRouting";
  contact
    "FRR Users List:       <mailto:frog@lists.frrouting.org>
     FRR Development List: <mailto:dev@lists.frrouting.org>";
  description
    "A model for FRR YANG module translators.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2018-07-31 {
    description
      "Initial revision.";
  }

  container frr-module-translator {
    leaf family {
      type string {
        length "0 .. 32";
      }
      mandatory true;
      description
        "Family of YANG models.";
    }
    list module {
      key "name";
      ordered-by user;
      description
        "YANG module.";

      leaf name {
        type string;
        description
          "Module name.";
      }
      leaf deviations {
        type string;
        mandatory true;
        description
          "Module containing the YANG deviations.";
      }
      list mappings {
        key "custom";
        description
          "YANG mappings between the custom module and FRR native modules.";

        leaf custom {
          type string {
            length "0 .. 256";
          }
          description
            "YANG path of the custom module.";
        }
        leaf native {
          type string {
            length "0 .. 256";
          }
          mandatory true;
          description
            "Corresponding path of the native YANG modules";
        }
      }
    }
  }
}
