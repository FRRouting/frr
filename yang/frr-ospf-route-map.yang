module frr-ospf-route-map {
  yang-version 1.1;
  namespace "http://frrouting.org/yang/ospf-route-map";
  prefix frr-ospf-route-map;

  import frr-route-map {
    prefix frr-route-map;
  }

  organization
    "Free Range Routing";
  contact
    "FRR Users List:       <mailto:frog@lists.frrouting.org>
     FRR Development List: <mailto:dev@lists.frrouting.org>";
  description
    "This module defines ospf route map settings";

  revision 2020-01-02 {
    description
      "Initial revision";

    reference
      "FRRouting";
  }

  identity metric-type {
    base frr-route-map:rmap-set-type;
    description
      "Set the type of metric";
  }

  augment "/frr-route-map:lib/frr-route-map:route-map/frr-route-map:entry/frr-route-map:set-action/frr-route-map:rmap-set-action/frr-route-map:set-action" {
    description
      "Augments the route map configuration to support setting metric types for OSPF6 routes";
    case metric-type {
      when "derived-from-or-self(../frr-route-map:action, 'metric-type')";
      leaf metric-type {
        type enumeration {
          enum "type-1" {
            value 0;
            description
              "OSPF6 external type 1 metric";
          }
          enum "type-2" {
            value 1;
            description
              "OSPF6 external type 2 metric";
          }
        }
        description
          "Specifies the metric type for the route map entry";
      }
    }
  }
}
