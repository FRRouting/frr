// SPDX-License-Identifier: BSD-2-Clause
module frr-eigrpd {
  yang-version 1.1;
  namespace "http://frrouting.org/yang/eigrpd";
  prefix frr-eigrpd;

  import ietf-inet-types {
    prefix inet;
  }
  import frr-interface {
    prefix frr-interface;
  }
  import frr-vrf {
    prefix frr-vrf;
  }
  import frr-route-map {
    prefix frr-route-map;
  }
  import frr-route-types {
    prefix frr-route-types;
  }
  import frr-filter {
    prefix frr-filter;
  }

  organization "FRRouting";
  contact
    "FRR Users List:       <mailto:frog@lists.frrouting.org>
     FRR Development List: <mailto:dev@lists.frrouting.org>";
  description
    "This module defines a model for managing FRR eigrpd daemon.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2019-09-09 {
    description
      "Changed interface references to use
      frr-interface:interface-ref typedef";
    reference
      "RFC 7868: Cisco's Enhanced Interior Gateway Routing Protocol (EIGRP).";
  }
  revision 2019-06-19 {
    description "Initial revision.";
    reference
      "RFC 7868: Cisco's Enhanced Interior Gateway Routing Protocol (EIGRP).";
  }

  /*
   * Types specification.
   */
  typedef autonomous-system {
    type uint16 {
      range "1..65535";
    }
    description "Administrative domain identification for a network";
  }

  feature openeigrp {
    description
      "Enable extended EIGRP configuration implemented by OpenEIGRP.
       The FRR legacy eigrpd does not enable this feature and retains
       its original callback requirements and classic configuration.";
  }

  typedef eigrp-redistribution-protocol {
    type enumeration {
      enum connected;
      enum static;
      enum rip;
      enum ospf;
      enum isis;
      enum bgp;
      enum eigrp;
    }
    description
      "Source routing protocols that Cisco EIGRP redistribution and the
       FRR EIGRP integration can represent.";
  }

  typedef eigrp-redistribution-route-instance {
    type uint16 {
      range "0..65535";
    }
    description
      "Normalized FRR route-instance carried with a redistributed route.
       Zero is the unqualified/no-route-instance value; a nonzero value is
       meaningful only for a source protocol whose FRR route entries carry
       a protocol instance.";
  }

  typedef authentication-type {
    type enumeration {
      enum none {
        value 0;
        description "Don't authenticate";
      }

      enum text {
        value 1;
        description "User defined text";
      }

      enum md5 {
        value 2;
        description "MD5 algorithm";
      }

      enum hmac-sha-256 {
        value 3;
        description "HMAC SHA256 algorithm";
      }
    }
    description "Authentication types";
  }

  /*
   * Named-mode address-family interface configuration.  The interface key is
   * a string because the Cisco named hierarchy also has the special
   * "af-interface default" template, which is not a host interface object.
   *
   * This augment intentionally appears before the eigrpd container. YANG
   * absolute-schema-nodeid augments are resolved against the completed module
   * schema, and keeping this patch away from the named parent/AF patch hunks
   * preserves independent patch detection during FRR installation.
   */
  augment "/eigrpd/named/address-family" {
    if-feature openeigrp;
    list af-interface {
      key "interface";
      description "Interface or default interface template configuration";

      leaf interface {
        type string {
          length "1..255";
        }
        description "Host interface name or the special default template";
      }

      leaf bandwidth-percent {
        type uint32 {
          range "1..999999";
        }
        description "Maximum percentage of interface bandwidth used by EIGRP";
      }

      leaf bandwidth {
        type uint32 {
          range "1..10000000";
        }
        units "kilobits per second";
        description "EIGRP interface bandwidth informational parameter";
      }

      leaf delay {
        type uint32 {
          range "1..16777215";
        }
        units "tens of microseconds";
        description "EIGRP interface throughput delay";
      }

      leaf hello-interval {
        type uint16 {
          range "1..65535";
        }
        units seconds;
        description "EIGRP hello interval";
      }

      leaf hold-time {
        type uint16 {
          range "1..65535";
        }
        units seconds;
        description "EIGRP neighbor hold time";
      }

      leaf passive-interface {
        type empty;
        description "Suppress EIGRP hello packets and updates";
      }

      leaf authentication-mode {
        type authentication-type;
        must ". != 'hmac-sha-256' or (../authentication-encryption-type and ../authentication-password)";
        description "EIGRP packet authentication mode";
      }

      leaf authentication-encryption-type {
        when "../authentication-mode = 'hmac-sha-256'";
        type uint8 { range "0 | 7"; }
        description "Cisco password encoding selector for HMAC SHA-256";
      }

      leaf authentication-password {
        when "../authentication-mode = 'hmac-sha-256'";
        type string { length "1..32"; }
        description "HMAC SHA-256 authentication password";
      }

      leaf authentication-key-chain {
        type string;
        description "Host key-chain name used for EIGRP authentication";
      }

      leaf next-hop-self {
        type boolean;
        default true;
        description "Advertise the local outbound interface as next hop";
      }

      leaf split-horizon {
        type boolean;
        default true;
        description "Enable EIGRP split horizon on this interface";
      }

      list summary-address {
        key "prefix";
        description "Manual summary configured on this address-family interface";

        leaf prefix {
          type inet:ip-prefix;
          description "IPv4 or IPv6 summary prefix";
        }

        leaf administrative-distance {
          type uint8 { range "1..255"; }
          description "Administrative distance for the summary route";
        }

        leaf leak-map {
          when "../administrative-distance";
          type string { length "1..255"; }
          description "Route-map used to leak component routes";
        }
      }

      leaf shutdown {
        type empty;
        description "Administratively disable EIGRP on this AF interface";
      }
    }
  }

  /*
   * EIGRP operational data.
   */
  container eigrpd {
    description "EIGRP daemon configuration";

    list instance {
      key "asn vrf";
      description "EIGRP autonomous system instance";
      leaf asn {
        type autonomous-system;
        description "Autonomous System Number";
      }

      leaf vrf {
        type frr-vrf:vrf-ref;
        description "Virtual Routing Domain name";
      }

      /*
       * Configurations.
       */
      leaf router-id {
        type inet:ipv4-address;
        description "Router identification";
      }

      leaf-list passive-interface {
        type frr-interface:interface-ref;
        description "List of suppressed interfaces";
      }

      leaf active-time {
        type uint16 {
          range "0..65535";
        }
        units seconds;
        default 180;
        description "ACTIVE time limit in seconds (0 disables limit)";
      }

      leaf variance {
        type uint8 {
          range "1..128";
        }
        description "Control load balance variance";
      }

      leaf maximum-paths {
        type uint8 {
          range "1..32";
        }
        description "Most number of paths to forward packets to";
      }

      leaf event-log-size {
        if-feature openeigrp;
        type uint32;
        description "Maximum number of EIGRP diagnostic events retained";
      }

      container metric-weights {
        description
          "Metrics and parameters for advertisement.

           EIGRP calculates the composite metric with the following formula:

               metric = 256 * ({(K1*BW) + [(K2*BW)/(256-LOAD)] + (K3*DELAY)} *
                        (K5/(REL+K4)))

           Composite calculation:
                                                                         K5
               metric =[(K1*Net-Throughput) + Latency)+(K6*ExtAttr)] * ------
                                                                       K4+Rel

           RFC 7868 Sections 5.5 and 5.6.2.5.";

        leaf K1 {
          type uint8 {
            range "0..255";
          }
          description "Bandwidth coefficient.";
        }

        leaf K2 {
          type uint8 {
            range "0..255";
          }
          description "Bandwidth on load coefficient.";
        }

        leaf K3 {
          type uint8 {
            range "0..255";
          }
          description "Delay or latency-based coefficient.";
        }

        leaf K4 {
          type uint8 {
            range "0..255";
          }
          description "Link quality coefficient.";
        }

        leaf K5 {
          type uint8 {
            range "0..255";
          }
          description "Packet loss coefficient.";
        }

        leaf K6 {
          type uint8 {
            range "0..255";
          }
          description "Jitter coefficient.";
        }
      }

      leaf-list network {
        type inet:ipv4-prefix;
        description "Enable EIGRP on the specific network";
      }

      leaf-list neighbor {
        type inet:ipv4-address;
        description "Specific EIGRP neighbor";
      }

      uses frr-filter:distribute-list-group;

      list redistribute {
        key "protocol";

        description "Redistribute routes learned from other routing protocols";

        leaf protocol {
          type frr-route-types:frr-route-types-v4;
          must '. != "eigrp"';
          description "Routing protocol";
        }

        leaf route-map {
          type frr-route-map:route-map-ref;
          description
            "Applies the conditions of the specified route-map to
             routes that are redistributed into the EIGRP routing
             instance";
        }

        container metrics {
          description "Metric for the redistributed routes";

          leaf bandwidth {
            type uint32 {
              range "1..4294967295";
            }
            description "Bandwidth metric in Kbits per second";
          }

          leaf delay {
            type uint32 {
              range "0..4294967295";
            }
            units microseconds;
            description "Delay metric";
          }

          leaf reliability {
            type uint32 {
              range "0..255";
            }
            description "Reliability metric";
          }

          leaf load {
            type uint32 {
              range "1..255";
            }
            description "Effective bandwidth usage";
          }

          leaf mtu {
            type uint32 {
              range "1..65535";
            }
            description "Path Maximum Transmission Unit";
          }
        }
      }
    }

    /*
     * EIGRP named-mode configuration.  This is intentionally separate from
     * the legacy numeric-AS instance list because one named parent may own
     * multiple IPv4/IPv6 address-family contexts.
     */
    list named {
      if-feature openeigrp;
      key "name";
      description "EIGRP named-mode parent process";

      leaf name {
        type string {
          length "1..64";
        }
        description "Case-sensitive local EIGRP process name";
      }

      list address-family {
        key "afi vrf asn";
        description "Address-family protocol context owned by a named process";

        leaf afi {
          type enumeration {
            enum ipv4 {
              value 4;
              description "IPv4 unicast address family";
            }
            enum ipv6 {
              value 6;
              description "IPv6 unicast address family";
            }
          }
          description "Network-layer address family";
        }

        leaf vrf {
          type frr-vrf:vrf-ref;
          description "Virtual Routing Domain name";
        }

        leaf asn {
          type autonomous-system;
          description "EIGRP autonomous-system number for this address family";
        }
      }
    }
  }

  /*
   * EIGRP interface configurations.
   */
   augment "/frr-interface:lib/frr-interface:interface" {
     description "Augments interface configuration with EIGRP parameters";

     container eigrp {
       description "EIGRP interface parameters";

       leaf delay {
         type uint32 {
           range "1..16777215";
         }
         default 10;
         description "Throughput delay";
       }

       leaf bandwidth {
         type uint32 {
           range "1..10000000";
         }
         default 100000;
         description "Interface bandwidth value";
       }

       leaf hello-interval {
         type uint16 {
           range "1..65535";
         }
         units seconds;
         default 5;
         description "Hello packet interval";
       }

       leaf hold-time {
         type uint16 {
           range "1..65535";
         }
         units seconds;
         default 15;
         description "Timeout amount to consider neighbor down";
       }

       leaf split-horizon {
         type boolean;
         default true;
         description "Perform split horizon loop preventing technique";
       }

       /*
        * Per AS configuration.
        */
       list instance {
         key "asn";

         description "Autonomous System specific configuration";

         leaf asn {
           type autonomous-system;
           description "Autonomous System Number";
         }

         leaf-list summarize-addresses {
           type inet:ipv4-prefix;
           description "Peform address summarization";
         }

         leaf authentication {
           type authentication-type;
           default "none";
           description "Authentication digest algorithm";
         }

         leaf keychain {
           type string;
           description "FRR key chain name to use with authentication";
         }
       }
     }
   }

  /*
   * Named-mode address-family configuration is augmented separately from
   * the parent/key patch so FRR patch detection remains independently
   * reversible as named-mode coverage grows.
   */
  augment "/eigrpd/named/address-family" {
    if-feature openeigrp;
    leaf router-id {
      type inet:ipv4-address;
      description "Router identification for this address-family context";
    }

    leaf-list network {
      type inet:ipv4-prefix;
      description "IPv4 networks enabled in this named address family";
    }

    list neighbor {
      key "address interface";
      description "Static EIGRP neighbor for this named address family";

      leaf address {
        type inet:ip-address;
        description "Neighbor IPv4 or IPv6 address";
      }

      leaf interface {
        type frr-interface:interface-ref;
        description "Interface used to reach the configured neighbor";
      }
    }

    /* EIGRP_STEP1_CONFIG_COMPLETE */
    list neighbor-policy {
      key "address";
      description "Per-neighbor EIGRP policy and metadata";
      leaf address { type inet:ip-address; }
      leaf description { type string { length "1..80"; } }
      container maximum-prefix {
        presence "Configure a per-neighbor prefix limit";
        leaf maximum { type uint32 { range "1..4294967295"; } mandatory true; }
        leaf threshold { type uint8 { range "1..100"; } }
        leaf warning-only { type empty; }
      }
    }

    container neighbor-maximum-prefix {
      presence "Configure a prefix limit for all neighbors";
      leaf maximum { type uint32 { range "1..4294967295"; } mandatory true; }
      leaf threshold { type uint8 { range "1..100"; } }
      leaf warning-only { type empty; }
      leaf dampened { type empty; }
      leaf reset-time { type uint16 { range "1..65535"; } }
      leaf restart { type uint16 { range "1..65535"; } }
      leaf restart-count { type uint16 { range "1..65535"; } }
    }

    leaf log-neighbor-changes {
      type boolean;
      description "Explicit neighbor adjacency-change logging state";
    }

    container log-neighbor-warnings {
      presence "Configure neighbor warning logging";
      leaf enabled { type boolean; mandatory true; }
      leaf interval { type uint16 { range "1..65535"; } }
    }

    container metric-weights {
      presence "Configure EIGRP metric coefficients";
      description "Address-family metric weights: TOS, K1 through K5, and optional RFC 7868 K6";
      leaf tos {
        type uint8 { range "0"; }
        mandatory true;
      }
      leaf K1 { type uint8; mandatory true; }
      leaf K2 { type uint8; mandatory true; }
      leaf K3 { type uint8; mandatory true; }
      leaf K4 { type uint8; mandatory true; }
      leaf K5 { type uint8; mandatory true; }
      leaf K6 { type uint8; }
    }

    leaf shutdown {
      type empty;
      description "Administratively disable this address-family context";
    }
  }


  /*
   * Named-mode base topology configuration.  Runtime behavior is owned by
   * common EIGRP targets; this schema retains the named configuration while
   * those targets are implemented incrementally.
   */
  augment "/eigrpd/named/address-family" {
    if-feature openeigrp;
    container topology {
      presence "Configure the EIGRP base topology";
      description "Base topology configuration for this named address family";

      leaf auto-summary {
        type empty;
        description "Enable automatic classful summarization";
      }

      container default-information-in {
        presence "Accept exterior or default routing information";
        leaf access-list { type string { length "1..255"; } }
      }

      container default-information-out {
        presence "Advertise exterior or default routing information";
        leaf access-list { type string { length "1..255"; } }
      }

      /* EIGRP_STEP1_TOPOLOGY_COMPOUND_MANDATORY */
      container default-metric {
        presence "Configure a default redistribution metric";
        leaf bandwidth {
          type uint32 { range "1..4294967295"; }
          mandatory true;
        }
        leaf delay {
          type uint32;
          mandatory true;
        }
        leaf reliability {
          type uint8;
          mandatory true;
        }
        leaf load {
          type uint8 { range "1..255"; }
          mandatory true;
        }
        leaf mtu {
          type uint16 { range "1..65535"; }
          mandatory true;
        }
      }

      container distance {
        presence "Configure EIGRP administrative distances";
        leaf internal {
          type uint8 { range "1..255"; }
          mandatory true;
        }
        leaf external {
          type uint8 { range "1..255"; }
          mandatory true;
        }
      }

      container maximum-prefix {
        presence "Configure a topology prefix limit";
        leaf maximum { type uint32 { range "1..4294967295"; } mandatory true; }
        leaf threshold { type uint8 { range "1..100"; } }
        leaf warning-only { type empty; }
        leaf dampened { type empty; }
        leaf reset-time { type uint16 { range "1..65535"; } }
        leaf restart { type uint16 { range "1..65535"; } }
        leaf restart-count { type uint16 { range "1..65535"; } }
      }

      leaf maximum-paths { type uint8 { range "1..32"; } }
      leaf metric-maximum-hops { type uint8 { range "1..255"; } }
      leaf metric-version-32bit { type empty; }
      leaf event-log-size { type uint32; }



      uses frr-filter:distribute-list-group;

      list offset-list {
        key "access-list direction interface";
        description "Metric offset applied to incoming or outgoing updates";
        leaf access-list {
          type string { length "1..255"; }
        }
        leaf direction {
          type enumeration {
            enum in;
            enum out;
          }
        }
        leaf interface {
          type string;
          description "Interface name, or empty for all interfaces";
        }
        leaf offset {
          type uint32 { range "0..2147483647"; }
          mandatory true;
        }
      }

      list redistribute {
        key "protocol route-instance";
        description "Routes redistributed into this EIGRP topology";
        leaf protocol {
          type eigrp-redistribution-protocol;
          description "Source routing protocol";
        }
        leaf route-instance {
          type eigrp-redistribution-route-instance;
          must "../protocol != 'eigrp' or . != 0" {
            error-message
              "EIGRP redistribution requires the source EIGRP AS as its route instance";
          }
          must "../protocol = 'eigrp' or ../protocol = 'ospf' or . = 0" {
            error-message
              "This source protocol has no distinct FRR route instance; use zero";
          }
          description
            "Source route-instance using FRR redistribution semantics. EIGRP
             uses the source AS as a nonzero route instance. OSPF may use its
             FRR process instance; zero represents an unqualified OSPF
             subscription. Connected, static, RIP, IS-IS, and BGP use zero
             because FRR does not carry a distinct route instance for those
             route types. A BGP ASN or IS-IS area tag is a protocol
             configuration identity, not an FRR route-instance value, and is
             not encoded in this key.";
        }
        leaf route-map {
          type string { length "1..255"; }
          description "Route-map applied to redistributed routes";
        }
        container metrics {
          presence "Configure an explicit redistribution metric";
          leaf bandwidth {
            type uint32 { range "1..4294967295"; }
            mandatory true;
          }
          leaf delay { type uint32; mandatory true; }
          leaf reliability { type uint8; mandatory true; }
          leaf load { type uint8 { range "1..255"; } mandatory true; }
          leaf mtu { type uint16 { range "1..65535"; } mandatory true; }
        }
      }

      container redistribute-maximum-prefix {
        presence "Configure a redistributed-route prefix limit";
        leaf maximum { type uint32 { range "1..4294967295"; } mandatory true; }
        leaf threshold { type uint8 { range "1..100"; } }
        leaf warning-only { type empty; }
        leaf dampened { type empty; }
        leaf reset-time { type uint16 { range "1..65535"; } }
        leaf restart { type uint16 { range "1..65535"; } }
        leaf restart-count { type uint16 { range "1..65535"; } }
      }

      list summary-metric {
        key "prefix";
        description "Fixed metric for an IPv4 or IPv6 summary aggregate";
        leaf prefix { type inet:ip-prefix; }
        leaf bandwidth { type uint32 { range "1..4294967295"; } }
        leaf delay { type uint32; }
        leaf reliability { type uint8; }
        leaf load { type uint8 { range "1..255"; } }
        leaf mtu { type uint16 { range "1..65535"; } }
        leaf distance { type uint8 { range "1..255"; } }
      }

      leaf active-time {
        type uint16;
        description "Active-state time limit in minutes; zero means disabled";
      }

      leaf traffic-share-balanced {
        type boolean;
        description "Whether unequal-cost eligible routes share traffic";
      }

      leaf variance {
        type uint8 { range "1..128"; }
      }
    }
  }

}
