module confd.frr-ripngd {
  namespace "urn:dummy";
  prefix "dummy";

  import tailf-common {
    prefix tailf;
  }
  import frr-ripngd {
    prefix frr-ripngd;
  }

  tailf:annotate-module "frr-ripngd" {
    tailf:annotate-statement "container[name='ripngd']" {
      tailf:annotate-statement "list[name='instance']" {
        tailf:annotate-statement "container[name='state']" {
          tailf:callpoint "state";
        }
      }
    }
    tailf:annotate-statement "rpc[name='clear-ripng-route']" {
      tailf:actionpoint "actionpoint";
    }
  }
}
