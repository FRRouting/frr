module confd.frr-ripd {
  namespace "urn:dummy";
  prefix "dummy";

  import tailf-common {
    prefix tailf;
  }
  import frr-ripd {
    prefix frr-ripd;
  }

  tailf:annotate-module "frr-ripd" {
    tailf:annotate-statement "container[name='ripd']" {
      tailf:annotate-statement "list[name='instance']" {
        tailf:annotate-statement "container[name='state']" {
          tailf:callpoint "state";
        }
      }
    }
    tailf:annotate-statement "rpc[name='clear-rip-route']" {
      tailf:actionpoint "actionpoint";
    }
  }
}
