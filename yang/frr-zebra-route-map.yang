// SPDX-License-Identifier: BSD-2-Clause
module frr-zebra-route-map {
  yang-version 1.1;
  namespace "http://frrouting.org/yang/zebra-route-map";
  prefix frr-zebra-route-map;

  import ietf-inet-types {
    prefix inet;
  }

  import frr-filter {
    prefix frr-filter;
  }

  import frr-route-map {
    prefix frr-route-map;
  }

  import frr-route-types {
    prefix frr-route-types;
  }

  organization
    "Free Range Routing";
  contact
    "FRR Users List:       <mailto:frog@lists.frrouting.org>
     FRR Development List: <mailto:dev@lists.frrouting.org>";
  description
    "This module defines zebra route map settings.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2026-04-07 {
    description
      "Match on next-hop's first seg6 segment (if any)
       and set the SRv6 encapsulation source address";

    reference
      "FRRouting";
  }

  revision 2020-01-02 {
    description
      "Initial revision";
    reference
      "FRRouting";
  }

  identity ipv4-prefix-length {
    base frr-route-map:rmap-match-type;
    description
      "Match IPv4 address prefix length";
  }

  identity ipv4-next-hop-prefix-length {
    base frr-route-map:rmap-match-type;
    description
      "Match IPv4 next-hop address prefix length";
  }

  identity ipv6-prefix-length {
    base frr-route-map:rmap-match-type;
    description
      "Match IPv6 address prefix length";
  }

  identity ipv4-next-hop-seg6-prefix-list {
    base frr-route-map:rmap-match-type;
    description
      "Match IPv4 next-hop's first seg6 segment";
  }

  identity ipv6-next-hop-seg6-prefix-list {
    base frr-route-map:rmap-match-type;
    description
      "Match IPv6 next-hop's first seg6 segment";
  }

  identity source-instance {
    base frr-route-map:rmap-match-type;
    description
      "Match the protocol's instance number";
  }

  identity source-protocol {
    base frr-route-map:rmap-match-type;
    description
      "Match protocol via which the route was learnt";
  }

  identity src-address {
    base frr-route-map:rmap-set-type;
    description
      "Set IPv4/IPv6 source address for route";
  }

  identity srv6-encap-source {
    base frr-route-map:rmap-set-type;
    description
      "Set the SRv6 encapsulation source address";
  }

  augment "/frr-route-map:lib"
    + "/frr-route-map:route-map"
    + "/frr-route-map:entry"
    + "/frr-route-map:match-condition"
    + "/frr-route-map:rmap-match-condition"
    + "/frr-route-map:match-condition" {
    description
      "Augment route-map match conditions with zebra-specific
       match types for prefix length, source instance, and
       source protocol.";
    case ipv4-prefix-length {
      when "derived-from-or-self(../frr-route-map:condition, 'frr-zebra-route-map:ipv4-prefix-length') or "
         + "derived-from-or-self(../frr-route-map:condition, 'frr-zebra-route-map:ipv4-next-hop-prefix-length')";
      leaf ipv4-prefix-length {
        type uint8 {
          range "0..32";
        }
        description
          "IPv4 prefix length (or next-hop prefix length) to match.
           Used for both ipv4-prefix-length and ipv4-next-hop-prefix-length
           match conditions.";
      }
    }

    case ipv6-prefix-length {
      when "derived-from-or-self(../frr-route-map:condition, 'frr-zebra-route-map:ipv6-prefix-length')";
      leaf ipv6-prefix-length {
        type uint8 {
          range "0..128";
        }
        description
          "IPv6 prefix length to match.";
      }
    }

    case source-instance {
      when "derived-from-or-self(../frr-route-map:condition, 'frr-zebra-route-map:source-instance')";
      leaf source-instance {
        type uint8 {
          range "0..255";
        }
        description
          "Protocol instance number to match.";
      }
    }

    case source-protocol {
      when "derived-from-or-self(../frr-route-map:condition, 'frr-zebra-route-map:source-protocol')";
      leaf source-protocol {
        type frr-route-types:frr-route-types;
        description
          "Protocol type via which the route was learnt.";
      }
    }

    case ipv4-next-hop-seg6-prefix-list {
      when "derived-from-or-self(../frr-route-map:condition, 'frr-zebra-route-map:ipv4-next-hop-seg6-prefix-list')";
      leaf ipv4-next-hop-seg6-prefix-list {
        type frr-filter:access-list-name;
      }
    }

    case ipv6-next-hop-seg6-prefix-list {
      when "derived-from-or-self(../frr-route-map:condition, 'frr-zebra-route-map:ipv6-next-hop-seg6-prefix-list')";
      leaf ipv6-next-hop-seg6-prefix-list {
        type frr-filter:access-list-name;
      }
    }
  }

  augment "/frr-route-map:lib"
    + "/frr-route-map:route-map"
    + "/frr-route-map:entry"
    + "/frr-route-map:set-action"
    + "/frr-route-map:rmap-set-action"
    + "/frr-route-map:set-action" {
    description
      "Augment route-map set actions with zebra-specific
       set action for source address.";
    case src-address {
      when "derived-from-or-self(../frr-route-map:action, 'frr-zebra-route-map:src-address')";
      choice src-address {
        description
          "Value of the source address";
        case ipv4-src-address {
          leaf ipv4-src-address {
            type inet:ipv4-address;
            mandatory true;
            description
              "IPv4 source address to set for the route.";
          }
        }

        case ipv6-src-address {
          leaf ipv6-src-address {
            type inet:ipv6-address;
            mandatory true;
            description
              "IPv6 source address to set for the route.";
          }
        }
      }
    }

    case srv6-encap-source {
      when "derived-from-or-self(../frr-route-map:action, 'frr-zebra-route-map:srv6-encap-source')";
      leaf srv6-encap-source {
        type inet:ipv6-address-no-zone;
        mandatory true;
      }
    }
  }
}
